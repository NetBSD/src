-- $Id: gssapi.asn1,v 1.1 2008/03/22 09:39:23 mlelstv Exp $

GSS-API DEFINITIONS ::= BEGIN

IMPORTS heim_any_set FROM heim;

GSSAPIContextToken ::= [APPLICATION 0] IMPLICIT SEQUENCE {
	thisMech OBJECT IDENTIFIER,
	innerContextToken heim_any_set
}

END
