-- $Id: pkcs10.asn1,v 1.1 2008/03/22 09:42:41 mlelstv Exp $
PKCS10 DEFINITIONS ::=

BEGIN

IMPORTS
	Name, SubjectPublicKeyInfo, Attribute, AlgorithmIdentifier
	FROM rfc2459;


CertificationRequestInfo ::= SEQUENCE {
    version       INTEGER { pkcs10-v1(0) },
    subject       Name,
    subjectPKInfo SubjectPublicKeyInfo,
    attributes    [0] IMPLICIT SET OF Attribute OPTIONAL 
}

CertificationRequest ::= SEQUENCE {
    certificationRequestInfo CertificationRequestInfo,
    signatureAlgorithm	     AlgorithmIdentifier,
    signature                BIT STRING
}

END
